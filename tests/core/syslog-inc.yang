submodule syslog-inc {
    /*
     * Copyright (c) 2003-2006, 2008, 2014 Juniper Networks, Inc.
     * All rights reserved.
     */

    grouping facilties-choices-except-any {
	enum authorization {
	    help "Authorization system";
	    option auth;
	}
	enum privileged {
	    help "Privileged authorization events";
	    hidden guru;
	    option authpriv;
	}
	enum cron {
	    help "Cron daemon";
	    hidden internal;
	}
	enum daemon {
	    help "Various system processes";
	}
	enum ftp {
	    help "FTP process";
	}
	enum ntp {
	    help "NTP process";
	}
	enum security {
	    help "Security related";
	}
	enum kernel {
	    help "Kernel";
	    option kern;
	}
	enum lpr {
	    help "Line printer spooling system";
	    hidden guru;
	}
	enum mail {
	    help "Mail system";
	    hidden guru;
	}
	enum news {
	    help "Network news system";
	    hidden guru;
	}
	enum syslog {
	    help "Internal use only";
	    hidden guru;
	}
	enum user {
	    help "User processes";
	}
	enum uucp {
	    help "UUCP system";
	    hidden guru;
	}
	enum local0 {
	    help "Local logging option number 0";
	    hidden guru;
	}
	enum dfc {
	    help "Dynamic flow capture";
	    alias local1;
	    option local1;
	}
	enum external {
	    help "Local external applications";
	    alias local2;
	    option "external";
	}
	enum firewall {
	    help "Firewall filtering system";
	    alias local3;
	    option local3;
	}
	enum pfe {
	    help "Packet Forwarding Engine";
	    alias local4;
	    option local4;
	}
	enum conflict-log {
	    help "Configuration conflict log";
	    alias local5;
	    option local5;
	}
	enum change-log {
	    help "Configuration change log";
	    alias local6;
	    option local6;
	}
	enum interactive-commands {
	    help "Commands executed by the UI";
	    option local7;
	}
    }

    grouping system-facility-attribute {
	key facility;
	leaf facility {
	    help "Facility type";
	    type enumeration {
		enum "any" {
		    help "All facilities";
		    option "*";
		}
		use facilties-choices-except-any;
	    }
        }
    }


    grouping services-facility-attribute {
	key facility;
	leaf facility {
	    help "Facility type";
	    type enumeration {
		enum services {
		    help "Adaptive Services PIC";
		}
            }
        }
    }

    grouping level-attribute {
	key leve;
	leaf level {
	    help "Level name";
	    type enumeration {
		enum "any" {
		    help "All levels";
		    option "*";
		}
		enum emergency {
		    help "Panic conditions";
		    option "emerg";
		}
		enum alert {
		    help "Conditions that should be corrected immediately";
		}
		enum critical {
		    help "Critical conditions";
		    option "crit";
		}
		enum error {
		    help "Error conditions";
		    option "err";
		}
		enum warning {
		    help "Warning messages";
		}
		enum notice {
		    help "Conditions that should be handled specially";
		}
		enum info {
		    help "Informational messages";
		}
		enum none {
		    help "No messages";
		}
		enum verbose {
		    hidden guru;
		    alias debug;
		    help "Verbose messages";
		    option debug;
		}
            }
        }
    }

    grouping level-choices-except-any-none {
	enum emergency {
	    help "Panic conditions";
	    option "emerg";
	}
	enum alert {
	    help "Conditions that should be corrected immediately";
	}
	enum critical {
	    help "Critical conditions";
	    option "crit";
	}
	enum error {
	    help "Error conditions";
	    option "err";
	}
	enum warning {
	    help "Warning messages";
	}
	enum notice {
	    help "Conditions that should be handled specially";
	}
	enum info {
	    help "Informational messages";
	}
	enum verbose {
	    hidden guru;
	    alias debug;
	    help "Verbose messages";
	    option debug;
	}
    }

    grouping facility-override-attribute {
	leaf facility-override {
	    help "Alternate facility for logging to remote host";
	    type enumeration {
		enum authorization {
		    help "Authorization system";
		    option auth;
		}
		enum privileged {
		    help "Privileged authorization events";
		    hidden guru;
		    option authpriv;
		}
		enum cron {
		    help "Cron daemon";
		    hidden internal;
		}
		enum daemon {
		    help "Various system processes";
		}
		enum ftp {
		    help "FTP process";
		}
		enum kernel {
		    help "Kernel";
		    option kern;
		}
		enum lpr {
		    help "Line printer spooling system";
		    hidden guru;
		}
		enum mail {
		    hidden guru;
		    help "Mail system";
		}
		enum news {
		    help "Network news system";
		    hidden guru;
		}
		enum syslog {
		    help "Internal use only";
		    hidden guru;
		}
		enum user {
		    help "User processes";
		}
		enum uucp {
		    help "Uucp system";
		    hidden guru;
		}
		enum local0 {
		    help "Local logging option number 0";
		}
		enum local1 {
		    help "Local logging option number 1";
		}
		enum local2 {
		    help "Local logging option number 2";
		}
		enum local3 {
		    help "Local logging option number 3";
		}
		enum local4 {
		    help "Local logging option number 4";
		}
		enum local5 {
		    help "Local logging option number 5";
		}
		enum local6 {
		    help "Local logging option number 6";
		}
		enum local7 {
		    help "Local logging option number 7";
		}
            }
        }
    }

    grouping structured-format {
	container structured-data {
	    help "Log system message in structured format";
	    flag allow-struct;

	    leaf format {
		flag nokeyword;
		cname sd_format;

		type enumeration {
		    enum brief {
			help "Omit English-language text from end of "
			    "logged message";
			value 1;
		    }

		    enum detail {
			help "Include English-language text at end of "
			     "logged message";
			value 2;
			hidden default;
		    }
		}
	    default detail;
	    }
	}                                                           
    }
}
