module foo {
    namespace "http://foo.example.net" {
        prefix foo;
    }
    contact "Phil Shafer";

    param $MAX = 100;
    param $test-default = 42;

    include base-02;

    augment protocols {
	container one {
	    must not(../two);
	    help "This is" + " a help string";
	    config true;
	}

        leaf test {
            help "test" + "ing";
	    must test + ing;
	    must "test + ing";
	    must "test" + "ing";
            type int {
		range "1" .. "100";
            }
            default $test-default;
            must . < $MAX;
        }
    }
}
