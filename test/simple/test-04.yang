// Contents of "acme-system.yang"
module acme-system {
    namespace "http://acme.example.com/system";
    prefix "acme";

    organization "ACME Inc.";
    contact "joe@acme.example.com";
    description
	"The module for entities implementing the ACME system.";

    revision 2007-06-09 {
	description "Initial revision.";
    }

    container system {
	leaf host-name {
	    type string;
	    description "Hostname for this system";
	}

	leaf-list domain-search {
	    type string;
	    description "List of domain names to search";
	}

	container login {
	    leaf message {
		type string;
		description
		    "Message given at start of login session";
	    }

	    list user {
		key "name";
		leaf name {
		    type string;
		}
		leaf full-name {
		    type string;
		}
		leaf class {
		    type string;
		}
	    }
	}
    }

    list interface {
	key "name";

	leaf name {
	    type string;
	}
	leaf speed {
	    type enumeration {
		enum 10m;
		enum 100m;
		enum auto;
	    }
	}
	leaf observed-speed {
	    type uint32;
	    config false;
	}
    }

    typedef percent {
	type uint8 {
	    range "0 .. 100";
	}
	description "Percentage";
    }
 
    leaf completed {
	type percent;
    }

    grouping target {
	leaf address {
	    type inet:ip-address;
	    description "Target IP address";
	}
	leaf port {
	    type inet:port-number;
	    description "Target port number";
	}
    }
 
    container peer {
	container destination {
	    uses target;
	}
    }

    container connection {
	container source {
	    uses target {
		refine "address" {
		    description "Source IP address";
		}
		refine "port" {
		    description "Source port number";
		}
	    }
	}
	container destination {
	    uses target {
		refine "address" {
		    description "Destination IP address";
		}
		refine "port" {
		    description "Destination port number";
		}
	    }
	}
    }

    container food {
	choice snack {
        case sports-arena {
            leaf pretzel {
                type empty;
            }
            leaf beer {
                type empty;
            }
        }
        case late-night {
            leaf chocolate {
                type enumeration {
                    enum dark;
                    enum milk;
                    enum first-available;
                }
            }
        }
	}
    }

    augment /system/login/user {
	when "class != 'wheel'";
	leaf uid {
	    type uint16 {
		range "1000 .. 30000";
	    }
	}
    }

    rpc activate-software-image {
	input {
	    leaf image-name {
		type string;
	    }
	}
	output {
	    leaf status {
		type string;
	    }
	}
    }

    notification link-failure {
	description "A link failure has been detected";
	leaf if-name {
		type leafref {
		    path "/interface/name";
		}
	    }
	leaf if-admin-status {
		type admin-status;
	    }
	leaf if-oper-status {
		type oper-status;
	    }
    }

    list server {
	key "name";
	unique "ip port";
	leaf name {
	    type string;
	}
	leaf ip {
	    type inet:ip-address;
	}
	leaf port {
	    type inet:port-number;
	}
    }

    container transfer {
	choice how {
	default interval;
	case interval {
	    leaf interval {
		type uint16;
	    default 30;
	    units minutes;
	    }
	}
	case daily {
	    leaf daily {
		type empty;
	    }
	    leaf time-of-day {
		type string;
		units 24-hour-clock;
	    default 1am;
	    }
	}
	case manual {
	    leaf manual {
		type empty;
	    }
	}
	}
    }

    container protocol {
	choice name {
	case a {
	    leaf udp {
		type empty;
	    }
	}
	case b {
	    leaf tcp {
		type empty;
	    }
	}
	}
    }

    feature local-storage {
	description
	    "This feature means the device supports local
               storage (memory, flash or disk) that can be used to
               store syslog messages.";
    }

    container syslog {
	leaf local-storage-limit {
	    if-feature local-storage;
	    type uint64;
	    units "kilobyte";
	    config false;
	    description
		"The amount of local storage that can be
                   used to hold syslog messages.";
	}
    }

    typedef my-decimal {
	type decimal64 {
	    fraction-digits 2;
	    range "1 .. 3.14 | 10 | 20..max";
	}
    }

    leaf string-node {
	type string {
	    length "0..4";
	    pattern "[0-9a-fA-F]*";
	}
    }

    leaf myenum {
	type enumeration {
	    enum zero;
	    enum one;
	    enum seven {
		value 7;
	    }
	}
    }

    leaf mybits {
	type bits {
	    bit disable-nagle {
		position 0;
	    }
	    bit auto-sense-speed {
		position 1;
	    }
	    bit 10-Mb-only {
		position 2;
	    }
	}
        default "auto-sense-speed";
    }

    list interface {
	key "name";
	leaf name {
	    type string;
	}
	leaf admin-status {
	    type admin-status;
	}
	list address {
	    key "ip";
	    leaf ip {
		type yang:ip-address;
	    }
	}
    }

    container default-address {
	leaf ifname {
	    type leafref {
		path "../../interface/name";
	    }
	}
	leaf address {
	    type leafref {
		path ../../interface[name = current()/../ifname]
		    /address/ip;
	    }
	}
    }          

    notification link-failure {
	leaf if-name {
		type leafref {
		    path "/interface/name";
		}
	    }
	leaf admin-status {
	    type leafref {
		path /interface[name = current()/../if-name]/admin-status;
	    }
	}
    }

    leaf union-node {
	type union {
	    type int32;
	    type enumeration {
		enum "unbounded";
	    }
	}
    }
}
