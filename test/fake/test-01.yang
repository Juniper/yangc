module foo {
    param $test-default = 15;
    param $test-min = 1;
    param $test-max = 100;

    namespace "http://foo.example.net" {
        prefix foo;
    }
    contact "Phil Shafer";

    augment protocols {
	container my-stuff {
	    leaf test {
		help "test help";
		type int {
		    range $test-min .. $test-max;
		}
		default $test-default;
		must some-function("test");
	    }

	    leaf-list funky {
		help "Funky stuff";
		type string;
	    }
	    leaf-list funky-too {
		description "More funky stuff";
		type string;
	    }
        }
    }
}
