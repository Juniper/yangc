submodule mchassic-inc.yang {
    /*
     * Copyright (c) 1998-2008,2014, Juniper Networks, Inc.
     * All rights reserved.
     *
     * Common definitions for typical multi-chassis YANG.
     * (Not exposed to External/SDK users)
     */

     /*
      * Protected system domain (formerly Hardware logical router)
      * related limits
      */
    param $MCHASSIS_UI_MIN_PSD_ID = 1;
    param $MCHASSIS_UI_MAX_PSD_ID = 31;
    param $MCHASSIS_UI_MAX_PSD_JCS_CHASSIS_ID = 4;
    param $MCHASSIS_UI_MAX_PSD_ROOT_DOMAIN_ID = 3;
    param $MCHASSIS_UI_MIN_PSD_JCS_SLOT_NUM = 1;
    param $MCHASSIS_UI_MAX_PSD_JCS_SLOT_NUM = 12;

    template mchassis-mandatory-arg-help-base ($help_str, $arg) {
	choice cid {
	    flag mandatory;
	    product $TX_SERIES;
	    copy-of $arg;
	    argument lcc {
		help $help_str;
		type uint {
		    range 0 .. $MCHASSIS_UI_MAX_LCC_SLOT;
		}
		action acceptable {
		    daemon mgd;
		    function mgd_is_switch_chassis;
		}
	    }

	    argument scc-dont-forward {
		type empty;
		hidden internal;
		action acceptable {
		    daemon mgd;
		    function mgd_is_switch_chassis;
		}
	    }
	}
    }

    template mchassis-all-mandatory-arg-help-base ($help_str, $arg) {
	call mchassis-mandatory-arg-help-base($help_str, $arg);
	augment cid {
	    argument "all-chassis" {
		help "Broadcast to all chassis";
		type empty;
		action acceptable {
		    daemon mgd;
		    function mgd_is_switch_chassis;
		}
	    }
        }
    }

    template mchassis-master-mandatory-arg-help-base ($help_str, $arg) {
	choice cid {
	    flag mandatory;
	    action acceptable {
		daemon mgd;
		function mgd_is_switch_chassis;
	    }
	    copy-of $arg;
	    argument lcc {
		help $help_str;
		type uint {
		    range 0 .. MCHASSIS_UI_MAX_LCC_SLOT;
		}
		action acceptable {
		    daemon mgd;
		    function mgd_is_switch_chassis;
		}
	    }

	    argument scc-dont-forward {
		type emtpy;
		hidden internal;
		action acceptable {
		    daemon mgd;
		    function mgd_is_switch_chassis;
		}
	    }
	}
    }

    template mchassis-arg-help-base ($help_str, $arg) {
	choice cid {
	    copy-of $arg;
	    argument lcc {
		help $help_str;
		type uint {
		    range 0 .. MCHASSIS_UI_MAX_LCC_SLOT;
		}
		action acceptable {
		    daemon mgd;
		    function mgd_is_switch_chassis;
		}
	    }
	    argument scc-dont-forward {
		type empty;
		hidden internal;
		action acceptable {
		    daemon mgd;
		    function mgd_is_switch_chassis;
		}
	    }
	}
    }

    template mchassis-dynamic-arg-help-base ($help_str, $param, $arg) {
	choice cid {
	    product $TX_SERIES;
	    action mandatory {
		daemon mgd;
		code "return (mgd_sibling_present(daap, \"" _ $param _ "\") "
		    "&& mgd_sibling_absent(daap, \"scc-dont-forward\"))";
	    }
	    copy-of $arg;
	    argument lcc {
		help $help_str;
		type uint {
		    range 0 .. MCHASSIS_UI_MAX_LCC_SLOT;
		}
		action acceptable {
		    daemon mgd;
		    function mgd_is_switch_chassis;
		}
	    }
	    argument scc-dont-forward {
		type empty;
		hidden internal;
		action acceptable {
		    daemon mgd;
		    function mgd_is_switch_chassis;
		}
	    }
	}
    }

    template mchassis-master-arg-help-base ($help_str, $arg) {
	choice cid {
	    action acceptable {
		daemon mgd;
		function mgd_is_switch_chassis;
	    }
	    copy-of $arg;
	    argument lcc {
		help $help_str;
		type uint {
		    range 0 .. MCHASSIS_UI_MAX_LCC_SLOT;
		}
		action acceptable {
		    daemon mgd;
		    function mgd_is_switch_chassis;
		}
	    }
	    argument scc-dont-forward {
		type empty;
		hidden internal;
		action acceptable {
		    daemon mgd;
		    function mgd_is_switch_chassis;
		}
	    }
	}
    }

    template is-valid-chassis-daemon ($daemon_name) {
        action acceptable {
	    daemon mgd;
	    code "return mgd_is_valid_chassis_daemon(" _ $daemon_name _ ")";
	}
    }
}

/*

/ *
 * The next two provide scc and lcc args to a command.
 * /
#define MCHASSIS_ARG_HELP(help)
        MCHASSIS_ARG_HELP_BASE(help, MCHASSIS_ARG_SCC(help));

#define MCHASSIS_DYNAMIC_ARG_HELP(help, param)
        MCHASSIS_DYNAMIC_ARG_HELP_BASE(help, param, MCHASSIS_ARG_SCC(help));

#define MCHASSIS_ARG_LCC_SCC_HELP(lcc_help, scc_help)
        MCHASSIS_ARG_HELP_BASE(lcc_help, MCHASSIS_ARG_SCC(scc_help));

#define MCHASSIS_MASTER_ARG_HELP(help)
        MCHASSIS_MASTER_ARG_HELP_BASE(help, MCHASSIS_ARG_SCC(help));

#define MCHASSIS_ARG_SHOW
        MCHASSIS_ARG_HELP("Display chassis-specific information");

#define MCHASSIS_DYNAMIC_ARG_SHOW(param)
        MCHASSIS_DYNAMIC_ARG_HELP("Display chassis-specific information", param);

#define MCHASSIS_MASTER_ARG_SHOW
        MCHASSIS_MASTER_ARG_HELP("Display chassis-specific information");

#define MCHASSIS_MANDATORY_ARG_HELP(help)
        MCHASSIS_MANDATORY_ARG_HELP_BASE(help, MCHASSIS_ARG_SCC(help));

#define MCHASSIS_ALL_MANDATORY_ARG_HELP(help)
        MCHASSIS_ALL_MANDATORY_ARG_HELP_BASE(help, MCHASSIS_ARG_SCC(help));

#define MCHASSIS_MASTER_MANDATORY_ARG_HELP(help)
        MCHASSIS_MASTER_MANDATORY_ARG_HELP_BASE(help, MCHASSIS_ARG_SCC(help));

#define MCHASSIS_MANDATORY_ARG_SHOW
        MCHASSIS_MANDATORY_ARG_HELP("Display chassis-specific information");

#define MCHASSIS_MASTER_MANDATORY_ARG_SHOW
        MCHASSIS_MASTER_MANDATORY_ARG_HELP("Display chassis-specific information");

/ *
 * This next macros provides lcc only args, no scc.
 * /
#define MCHASSIS_LCC_ARG_HELP(help_str)
        MCHASSIS_ARG_HELP_BASE(help_str, );

#define MCHASSIS_LCC_SHOW(help)
        MCHASSIS_ARG_HELP_BASE(help, );

#define MCHASSIS_DYNAMIC_LCC_SHOW(param, help)
        MCHASSIS_DYNAMIC_ARG_HELP_BASE(help, param, );

#define MCHASSIS_MANDATORY_LCC_ARG_HELP(help_str)
        MCHASSIS_MANDATORY_ARG_HELP_BASE(help_str, );

#define MCHASSIS_MANDATORY_LCC_SHOW
        MCHASSIS_MANDATORY_ARG_HELP_BASE("Display chassis-specific information", );

*/
